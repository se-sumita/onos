module org-openroadm-alarm {
  namespace "urn:org:openroadm:alarm";
  prefix org-openroadm-alarm;

  import ietf-yang-types {
    prefix yang;
    revision-date 2013-07-15;
  }
  import org-openroadm-common-types {
    prefix org-openroadm-common-types;
    revision-date 2017-12-15;
  }
  import org-openroadm-resource {
    prefix org-openroadm-resource;
    revision-date 2017-12-15;
  }
  import org-openroadm-probable-cause {
    prefix org-openroadm-probable-cause;
    revision-date 2017-12-15;
  }

  organization
    "Open ROADM MSA";
  contact
    "OpenROADM.org";
  description
    "YANG definitions of an alarm.
     
     Copyright of the Members of the Open ROADM MSA Agreement dated (c) 2016, 
     AT&T Intellectual Property.  All other rights reserved.
     
     Redistribution and use in source and binary forms, with or without modification, 
     are permitted provided that the following conditions are met:
     
     * Redistributions of source code must retain the above copyright notice, this 
       list of conditions and the following disclaimer.
     * Redistributions in binary form must reproduce the above copyright notice, 
       this list of conditions and the following disclaimer in the documentation and/or 
       other materials provided with the distribution.
     * Neither the Members of the Open ROADM MSA Agreement nor the names of its 
       contributors may be used to endorse or promote products derived from this software 
       without specific prior written permission.
     
     THIS SOFTWARE IS PROVIDED BY THE MEMBERS OF THE OPEN ROADM MSA  AGREEMENT ''AS IS'' 
     AND ANY EXPRESS OR IMPLIED WARRANTIES, INCLUDING, BUT NOT LIMITED TO, THE IMPLIED 
     WARRANTIES OF MERCHANTABILITY AND FITNESS FOR A PARTICULAR PURPOSE ARE DISCLAIMED. 
     IN NO EVENT THE MEMBERS OF THE OPEN ROADM MSA  AGREEMENT BE LIABLE FOR ANY DIRECT, 
     INDIRECT, INCIDENTAL, SPECIAL, EXEMPLARY, OR CONSEQUENTIAL DAMAGES (INCLUDING, BUT 
     NOT LIMITED TO, PROCUREMENT OF SUBSTITUTE GOODS OR SERVICES;  LOSS OF USE, DATA, 
     OR PROFITS; OR BUSINESS INTERRUPTION) HOWEVER CAUSED AND ON ANY THEORY OF LIABILITY, 
     WHETHER IN CONTRACT, STRICT LIABILITY, OR TORT (INCLUDING NEGLIGENCE OR OTHERWISE) 
     ARISING IN ANY WAY OUT OF THE USE OF THIS SOFTWARE, EVEN IF ADVISED OF THE 
     POSSIBILITY OF SUCH DAMAGE.";

  revision 2017-12-15 {
    description
      "Version 2.2";
  }
  revision 2017-09-29 {
    description
      "Version 2.1";
  }
  revision 2017-07-28 {
    description
      "Version 2.0.1 - added revision-date to imports";
  }
  revision 2016-10-14 {
    description
      "Version 1.2";
  }

  grouping alarm {
    leaf id {
      type string;
      mandatory true;
      description
        "Uniquely id for this alarm, within the given management domain";
    }
    container resource {
      description
        "Resource under alarm";
      uses org-openroadm-resource:resource;
    }
    container probableCause {
      description
        "Probable cause of alarm";
      uses org-openroadm-probable-cause:probable-cause;
    }
    leaf raiseTime {
      type yang:date-and-time;
      mandatory true;
      description
        "Time alarm was raised";
    }
    leaf severity {
      type org-openroadm-common-types:severity;
      mandatory true;
      description
        "Severity of alarm. Based on X.733 perceived severity.";
    }
    leaf circuit-id {
      type string;
      description
        "Circuit-id for alarm correlation.";
    }
    leaf additional-detail {
      type string;
      description
        "Provide additional descriptive text about the probable cause.";
    }
    leaf corrective-action {
      type string;
      description
        "Provide recommended corrective actions for this probable cause, i.e. replace or restart a circuit pack, check wiring for the reported source, or secondary failure to be correlated ";
    }
  }

  notification alarm-notification {
    description
      "Notification sent on initial alarm creation, as well as any time the alarm changes state, including clear";
    uses alarm;
  }
  container active-alarm-list {
    config false;
    description
      "List of currently active alarms. An alarm is removed from this table when the state transitions to clear.";
    list activeAlarms {
      key "id";
      uses alarm;
    }
  }
}
