module org-openroadm-tca {
  namespace "urn:org:openroadm:tca";
  prefix org-openroadm-tca;

  import ietf-yang-types {
    prefix yang;
    revision-date 2013-07-15;
  }
  import org-openroadm-common-types {
    prefix org-openroadm-common-types;
    revision-date 2017-12-15;
  }
  import org-openroadm-pm-types {
    prefix org-openroadm-pm-types;
    revision-date 2017-12-15;
  }
  import org-openroadm-resource {
    prefix org-openroadm-resource;
    revision-date 2017-12-15;
  }

  organization
    "Open ROADM MSA";
  contact
    "OpenROADM.org";
  description
    "YANG definitions of Threshold Crossing Alert types.
       
      Copyright of the Members of the Open ROADM MSA Agreement dated (c) 2016, 
      AT&T Intellectual Property.  All other rights reserved.
      
      Redistribution and use in source and binary forms, with or without modification, 
      are permitted provided that the following conditions are met:
      
      * Redistributions of source code must retain the above copyright notice, this 
        list of conditions and the following disclaimer.
      * Redistributions in binary form must reproduce the above copyright notice, 
        this list of conditions and the following disclaimer in the documentation and/or 
        other materials provided with the distribution.
      * Neither the Members of the Open ROADM MSA Agreement nor the names of its 
        contributors may be used to endorse or promote products derived from this software 
        without specific prior written permission.
      
      THIS SOFTWARE IS PROVIDED BY THE MEMBERS OF THE OPEN ROADM MSA  AGREEMENT ''AS IS'' 
      AND ANY EXPRESS OR IMPLIED WARRANTIES, INCLUDING, BUT NOT LIMITED TO, THE IMPLIED 
      WARRANTIES OF MERCHANTABILITY AND FITNESS FOR A PARTICULAR PURPOSE ARE DISCLAIMED. 
      IN NO EVENT THE MEMBERS OF THE OPEN ROADM MSA  AGREEMENT BE LIABLE FOR ANY DIRECT, 
      INDIRECT, INCIDENTAL, SPECIAL, EXEMPLARY, OR CONSEQUENTIAL DAMAGES (INCLUDING, BUT 
      NOT LIMITED TO, PROCUREMENT OF SUBSTITUTE GOODS OR SERVICES;  LOSS OF USE, DATA, 
      OR PROFITS; OR BUSINESS INTERRUPTION) HOWEVER CAUSED AND ON ANY THEORY OF LIABILITY, 
      WHETHER IN CONTRACT, STRICT LIABILITY, OR TORT (INCLUDING NEGLIGENCE OR OTHERWISE) 
      ARISING IN ANY WAY OUT OF THE USE OF THIS SOFTWARE, EVEN IF ADVISED OF THE 
      POSSIBILITY OF SUCH DAMAGE";

  revision 2017-12-15 {
    description
      "Version 2.2";
  }
  revision 2017-09-29 {
    description
      "Version 2.1";
  }
  revision 2017-08-28 {
    description
      "Version 2.0.2 - added back the missing pmParameterName container";
  }
  revision 2017-07-28 {
    description
      "Version 2.0.1 - added revision-date to imports";
  }
  revision 2017-06-26 {
    description
      "Version 2.0";
  }
  revision 2016-10-14 {
    description
      "Version 1.2";
  }

  grouping tca {
    leaf id {
      type string;
      mandatory true;
    }
    container resource {
      uses org-openroadm-resource:resource;
    }
    container pmParameterName {
      uses org-openroadm-pm-types:pm-names;
    }
    leaf granularity {
      type org-openroadm-pm-types:pm-granularity;
      mandatory true;
    }
    leaf location {
      type org-openroadm-common-types:location;
      mandatory true;
    }
    leaf direction {
      type org-openroadm-common-types:direction;
      mandatory true;
    }
  }

  grouping potential-tca {
    uses tca;
    leaf lowThresholdValue {
      type org-openroadm-pm-types:pm-data-type;
    }
    leaf highThresholdValue {
      type org-openroadm-pm-types:pm-data-type;
    }
  }

  notification tca-notification {
    uses tca;
    leaf thresholdValue {
      type org-openroadm-pm-types:pm-data-type;
      mandatory true;
    }
    leaf thresholdType {
      type enumeration {
        enum "high" {
          value 1;
        }
        enum "low" {
          value 2;
        }
      }
      mandatory true;
      description
        "Threshold Crossed";
    }
    leaf pmParameterValue {
      type org-openroadm-pm-types:pm-data-type;
      mandatory true;
    }
    leaf raiseTime {
      type yang:date-and-time;
      mandatory true;
    }
  }
  container potential-tca-list {
    description
      "This is the set of threshold crossing alerts monitored on the device. Alerts are
       enabled/disabled by adding/deleting the high/low threshold values from the list.";
    list tca {
      key "id";
      uses potential-tca;
    }
  }
}
